module ietf-otn-slice {
     yang-version 1.1;
     namespace
       "urn:ietf:params:xml:ns:yang:ietf-otn-slice";
     prefix "otns";

     import ietf-network {
       prefix "nw";
       reference 
         "RFC 8345: A YANG Data Model for Network Topologies";
     }
     import ietf-network-topology {
       prefix "nt";
       reference
         "RFC 8345: A YANG Data Model for Network Topologies";
     }

     import ietf-layer1-types {
       prefix "l1-types";
       reference
         "draft-ietf-ccamp-layer1-types-14: 
          A YANG Data Model for Layer 1 Types";
     }

     import ietf-network-slice-service {
       prefix "ietf-nss";
       reference
         "draft-ietf-teas-ietf-network-slice-nbi-yang-25:
          A YANG Data Model for the RFC 9543 Network Slice Service";
     }

     import ietf-ns-topo {
       prefix "ns-topo";
       reference
         "draft-ietf-teas-network-slice-topology-yang-01:
          IETF Network Slice Topology YANG Data Model";
     }
      
     organization
       "IETF CCAMP Working Group";
     contact
       "WG Web: <http://tools.ietf.org/wg/ccamp/>
        WG List: <mailto:ccamp@ietf.org>

        Editor: Haomian Zheng
                <mailto:zhenghaomian@huawei.com>

        Editor: Italo Busi
                <mailto:italo.busi@huawei.com>

        Editor: Aihua Guo
                <mailto:aihuaguo.ietf@gmail.com>

        Editor: Sergio Belotti
                <mailto:sergio.belotti@nokia.com>";

     description
       "This module defines a YANG data model for configuring 
        technology-specific network slices in optical transport
        networks, e.g., Optical Transport Network (OTN).

        The model fully conforms to the Network Management Datastore
        Architecture (NMDA).

        Copyright (c) 2022 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

        This version of this YANG module is part of RFC XXXX; see the
        RFC itself for full legal notices.";

     revision "2025-07-03" {
       description
         "Latest revision of NBI YANG model for OTN slicing.";
       reference
         "draft-ietf-ccamp-yang-otn-slicing-09: Framework and Data
          Model for OTN Network Slicing";
     }


     /*
      * Identities
      */
     identity bit-error-rate {
       base ietf-nss:service-slo-metric-type;
       description
         "ODU bit error rate";
     }

     identity odu-tca-threshold-type {
       description
         "Base identity for ODU performance counter";
     }
     
     identity odu-bbe {
       base odu-tca-threshold-type;
       description
         "ODU Background Block Error (BBE) threshold";
     }
     
     identity odu-es {
       base odu-tca-threshold-type;
       description
         "ODU Errored Seconds (ES) threshold";
     }
     
     identity odu-ses {
       base odu-tca-threshold-type;
       description
         "ODU Severely Errored Seconds (SES) threshold";
     }

     identity odu-uas {
       base odu-tca-threshold-type;
       description
         "ODU Unavailable Seconds (UAS) threshold";
     }

     identity odu-ber {
       base odu-tca-threshold-type;
       description
         "ODU Bit Error Rate (BER) threshold";
     }

     identity pm-duration {
       description
         "Base identity for ODU performance monitoring interval";
     }
     
     identity pm-15m {
       base pm-duration;
       description
         "15 minuites pm duration";
     }

     identity pm-24h {
       base pm-duration;
       description
         "24 hours pm duration";
     }

     /*
      * Groupings
      */
     grouping odu-signal-quality {
       description
         "Grouping for ODU signal quality.";
 
       container odu-signal-quality {
         description
           "Contianer for ODU signal quality attributes.";
   
         list odu-pm-objective {
           key "duration pm-type";
           description
             "List of ODU performance requirements.";
           leaf duration {
             type identityref {
               base pm-duration;
             }
             description
               "Time duration.";
           }
           leaf pm-type {
             type identityref {
               base odu-tca-threshold-type;
             }
             description
               "ODU PM metric type.";
           }
           
           leaf pm-threshold {
             type uint64;
             description
               "ODU PM metric threshold.";
           }
         }
       }
     }

     grouping otn-slice-slo-policy {
       description
         "Policy grouping for OTN network slices.";

       container otn {
         description
           "OTN technology-specific SLO/SLE policy container";
   
         uses odu-signal-quality;
         uses l1-types:otn-link-bandwidth;
       }
     }

     /*
      * Augmented data nodes
      */
     /* slice template */
     augment "/ietf-nss:network-slice-services" +
             "/ietf-nss:slo-sle-templates" +
             "/ietf-nss:slo-sle-template" + 
             "/ietf-nss:slo-policy" {
       description
          "Augment IETF network slice service templates with
           OTN technology-specific SLO/SLE policy attributes.";
  
       uses otn-slice-slo-policy;
     }

     /* slice augments */
     augment "/ietf-nss:network-slice-services" +
             "/ietf-nss:slice-service" +
             "/ietf-nss:slo-sle-policy" + 
             "/ietf-nss:custom" + 
             "/ietf-nss:service-slo-sle-policy" +
             "/ietf-nss:slo-policy" {
       description
         "Augment IETF network slice services to include technology-
          specific SLO/SLE policy for connectivity-based OTN
          slices.";
          
       uses otn-slice-slo-policy;
     }

     /* network topology augments */
     augment "/nw:networks/nw:network" +
             "/ns-topo:slo-sle-policy" +
             "/ns-topo:custom" +
             "/ns-topo:service-slo-sle-policy" +
             "/ns-topo:slo-policy" {
       when "../../nw:network-types/ns-topo:network-slice" {
         description "Augment only for Network Slice topology.";
       }
       description "Augment topology configuration and state.";
       uses otn-slice-slo-policy;
     }

     /* network node augments */
     augment "/nw:networks/nw:network/nw:node" +
             "/ns-topo:slo-sle-policy" + 
             "/ns-topo:custom" + 
             "/ns-topo:service-slo-sle-policy" +
             "/ns-topo:slo-policy" {
       when "../../../nw:network-types/ns-topo:network-slice" {
         description "Augment only for Network Slice topology.";
       }
       description "Augment node configuration and state.";
       uses otn-slice-slo-policy;
     }

     /* network node's termination point augments */
     augment "/nw:networks/nw:network/nw:node" +
             "/nt:termination-point" +
             "/ns-topo:slo-sle-policy" + 
             "/ns-topo:custom" + 
             "/ns-topo:service-slo-sle-policy" +
             "/ns-topo:slo-policy" {
       when "../../../../nw:network-types/ns-topo:network-slice" {
         description "Augment only for Network Slice topology.";
       }
       description "Augment node configuration and state.";
	   
       uses otn-slice-slo-policy;
     }

     /* network link augments */
     augment "/nw:networks/nw:network/nt:link" +
             "/ns-topo:slo-sle-policy" + 
             "/ns-topo:custom" + 
             "/ns-topo:service-slo-sle-policy" +
             "/ns-topo:slo-policy" {
       when "../../../nw:network-types/ns-topo:network-slice" {
         description "Augment only for Network Slice topology.";
       }
       description "Augment link configuration and state.";
       uses otn-slice-slo-policy;
     }
     
     /* connectivity construct augments */
     augment "/ietf-nss:network-slice-services" +
             "/ietf-nss:slice-service" +
             "/ietf-nss:connection-groups" +
             "/ietf-nss:connection-group" +
             "/ietf-nss:slo-sle-policy" + 
             "/ietf-nss:custom" + 
             "/ietf-nss:service-slo-sle-policy" +
             "/ietf-nss:slo-policy" {
       description
         "Augment IETF network slice services to include technology-
          specific SLO/SLE policy for connection groups within
          a connectivity-based transport network slice.";
       uses otn-slice-slo-policy;
     }

     augment "/ietf-nss:network-slice-services" +
             "/ietf-nss:slice-service" +
             "/ietf-nss:connection-groups" +
             "/ietf-nss:connection-group" +
             "/ietf-nss:connectivity-construct" +
             "/ietf-nss:slo-sle-policy" + 
             "/ietf-nss:custom" + 
             "/ietf-nss:service-slo-sle-policy" +
             "/ietf-nss:slo-policy" {
       description
         "Augment IETF network slice services to include technology-
          specific SLO/SLE policy for connectivity-constructs within
          a connectivity-based transport network slice.";
       uses otn-slice-slo-policy;
     }
     
     augment "/ietf-nss:network-slice-services" +
             "/ietf-nss:slice-service" +
             "/ietf-nss:connection-groups" +
             "/ietf-nss:connection-group" +
             "/ietf-nss:connectivity-construct" +
             "/ietf-nss:type" +
             "/ietf-nss:a2a" +
             "/ietf-nss:a2a-sdp" +
             "/ietf-nss:slo-sle-policy" + 
             "/ietf-nss:custom" + 
             "/ietf-nss:service-slo-sle-policy" +
             "/ietf-nss:slo-policy" {
       description
         "Augment IETF network slice services to include technology-
          specific SLO/SLE policy for a2a connectivity-constructs
          within a connectivity-based transport network slice.";
       uses otn-slice-slo-policy;
     }
   }
